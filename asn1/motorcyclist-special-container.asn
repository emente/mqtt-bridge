-- Draft V0.0.4_2.2.1 - TS 103 300-3 
-- Based on the official version available at @url https://forge.etsi.org/rep/ITS/asn1/vam-ts103300_3/-/tree/v2.1.1
-- Modified to import from the CDD module V2.1.1

-- This module defines a special container for motorcycles, to be integrated into the 
-- Cooperative Awareness Message (CAM) defined in ETSI TS 103 900

VRU-Motorcyclist-Special-Container {itu-t(0) identified-organization(4) etsi(0) itsDomain(5)
    wg1(1) 103300 motorcyclist-special-container(2) version2(2)}


DEFINITIONS AUTOMATIC TAGS ::= 

BEGIN

IMPORTS
    PathPredicted, SequenceOfSafeDistanceIndication,
    StabilityChangeIndication, Wgs84Angle, CartesianAngle,
    VruSizeClass, VruSubProfileMotorcyclist
FROM ETSI-ITS-CDD 
    {itu-t(0) identified-organization(4) etsi(0)
     itsDomain(5) wg1(1) 102894 cdd(2) major-version-3(3) minor-version-1(1)}
;

MotorcylistSpecialContainer ::= SEQUENCE {
   motorcyclist                VruSubProfileMotorcyclist,
   sizeClass                   VruSizeClass,
   rollAngle                   CartesianAngle OPTIONAL, 
   orientation                 Wgs84Angle OPTIONAL,
   safeDistance                SequenceOfSafeDistanceIndication OPTIONAL,
   pathPrediction              PathPredicted OPTIONAL,
   stabilityChangeIndication   StabilityChangeIndication OPTIONAL,
   ...
}



END

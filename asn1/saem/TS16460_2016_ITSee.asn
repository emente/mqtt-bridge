--<OSS.PDU>--
 
-- First edition 2016


ITSee { iso (1) standard (0) localized(16460) ee(4) version0 (0)} 
DEFINITIONS AUTOMATIC TAGS ::= 
BEGIN

/* Quality check info:
Proper syntax and correct mapping of UPER on the intended binary presentation as specified in the main body of this document was validated with the OSS ASN.1 Studio tool.
*/

IMPORTS

ChannelInfo FROM ITSsa { iso (1) standard (0) localized(16460) sa(2) version0 (0)}  

MedType FROM CALMllsap {iso(1) standard(0) calm-ll-sap(21218) asnm-1 (1) version1 (1)}
;
-- End of IMPORTS

-- Extension Elements CLASS and reference value definitions 
-- CLASS
EXT-TYPE ::= CLASS {
      &extRef RefExt UNIQUE,
      &ExtValue
	}
	WITH SYNTAX {&ExtValue IDENTIFIED BY &extRef}

-- General extension (profiling)
Extension {EXT-TYPE : ExtensionTypes} ::= SEQUENCE {
	extensionId	EXT-TYPE.&extRef({ExtensionTypes}),
	value	EXT-TYPE.&ExtValue({ExtensionTypes}{@.extensionId})
	}
-- ExtensionTypes are specified for SAM, SRM, and LM

-- Reference values (for all types of extensions)
RefExt::=INTEGER (0..255)

c-Reserved	RefExt ::= 0
c-TxPowerUsed80211	RefExt ::= 4 -- LM-N-Header, SAM Header
c-2Dlocation	RefExt ::= 5 -- SAM Header
c-3Dlocation	RefExt ::= 6 -- SAM Header
c-advertiserID	RefExt ::= 7 -- SAM Header
c-ProviderServContext	RefExt ::= 8 -- SAM Service Info
c-IPv6Address	RefExt ::= 9 -- SAM Service Info
c-servicePort	RefExt ::= 10 -- SAM Service Info
c-ProviderMACaddress	RefExt ::= 11 -- SAM Service Info
c-EDCAparameterSet	RefExt ::= 12 -- SAM Channel Info
c-SecondaryDNS	RefExt ::= 13 -- SAM Routing Advertisement
c-GatewayMACaddress	RefExt ::= 14 -- SAM Routing Advertisement
c-ChannelNumber80211	RefExt ::= 15 -- LM-N-Header
c-DataRate80211	RefExt ::= 16 -- LM-N-Header
c-RepeatRate	RefExt ::= 17 -- SAM Header
c-CountryString	RefExt ::= 18 -- SAM Header
c-RCPIthreshold	RefExt ::= 19 -- SAM Service Info
c-WSAcountThreshold	RefExt ::= 20 -- SAM Service Info
c-ChannelAccess	RefExt ::= 21 -- SAM Channel Info
c-WSAcountThresInt	RefExt ::= 22 -- SAM Service Info
c-ChannelLoad 	RefExt ::= 23 -- SAE / CAMP / 1609 are working on this
c-LMtxCip	RefExt ::= 80 -- LM-N-Header 
c-LMrxCip	RefExt ::= 81 -- LM-N-Header 
c-LMchannelBusyRatio	RefExt ::= 82 -- LM-N-Header 
c-LMpacketID	RefExt ::= 83 -- LM-T-Header 
c-ExtendedChannelInfos	RefExt ::= 84 -- SAM Header
c-SAMapplicationData	RefExt ::= 85 -- SAM Service Info

-- all other values of	RefExt are reserved

-- ChannelLoad specification is not yet available.


-- LM extension elements

DataRate80211::=INTEGER(0..255)

TXpower80211::=INTEGER(-128..127)

ChannelNumber80211::=INTEGER(0..255)

LMchannelBusyRatio::=INTEGER{
	zeroPercent	(0),
	halfPercent	(1),
	onePercent	(2),
	hundredPercent	(200),
	unknown	(201)
	}(0..255) -- values larger than 201 are prohibited


-- SAM header extension elements

RepeatRate ::= INTEGER (0..255)

TwoDLocation ::= SEQUENCE {
	latitude 	Latitude,
	longitude 	Longitude
	}

ThreeDLocation ::= SEQUENCE {
	latitude 	Latitude,
	longitude 	Longitude,
	elevation	Elevation
	}

-- max. 32 octets are allowed in AdvertiserIdentifier!!!
-- 32 characters may produce more than 32 octets in UPER
AdvertiserIdentifier ::= UTF8String (SIZE (1..32))


-- Extended Channel Info
CHINFO-TYPE ::= CLASS {
	&id 		MedType UNIQUE,
	&Type
	}
	WITH SYNTAX {&Type IDENTIFIED BY &id}

chInfoType-unknown	MedType ::= unknown -- 0
chInfoType-any	MedType ::= any -- 1
chInfoType-2G	MedType ::= iso21212 -- 2
chInfoType-3G	MedType ::= iso21213 -- 3
chInfoType-IR	MedType ::= iso21214 -- 4
chInfoType-M5	MedType ::= iso21215 -- 5
chInfoType-MM	MedType ::= iso21216 -- 6
chInfoType-80216e	MedType ::= iso25112 -- 7
chInfoType-HC-SDMA	MedType ::= iso25113 -- 8
chInfoType-80220	MedType ::= iso29283 -- 9
chInfoType-LTE	MedType ::= iso17515 -- 10
chInfoType-6LowPan	MedType ::= iso19079 -- 11
chInfoType-15628	MedType ::= iso15628 -- 128
chInfoType-CAN	MedType ::= can -- 254
chInfoType-Ethernet	MedType ::= ethernet -- 255


ChInfoTypes CHINFO-TYPE ::= {
	{ NULL	IDENTIFIED BY chInfoType-unknown } |
	{ NULL	IDENTIFIED BY chInfoType-any } |
	{ ChannelInfo	IDENTIFIED BY chInfoType-M5 } ,
	...
	}

ExtendedChannelInfos ::= SEQUENCE OF ExtendedChannelInfo

ExtendedChannelInfo ::= SEQUENCE {
	medId	CHINFO-TYPE.&id({ChInfoTypes}), -- medium identifier
	value	CHINFO-TYPE.&Type({ChInfoTypes}{@.medId})
	}

--ServiceInfo extension elements
ProviderServiceContext ::= SEQUENCE{
    fillBit	BIT STRING (SIZE(3)), -- all bits set to zero!
    psc	OCTET STRING (SIZE(0..31)) -- size zero is not recommended
    }

IPv6Address ::= OCTET STRING (SIZE (16))

ServicePort ::= INTEGER (0..65535)

ProviderMacAddress ::= MACaddress

MACaddress ::= OCTET STRING (SIZE(6))

RcpiThreshold ::= INTEGER (0..255) -- see IEEE Std 802.11

WsaCountThreshold ::= INTEGER (0..255)

WsaCountThresholdInterval ::= INTEGER (0..255) -- value 0 is not used

SAMapplicationData ::= OCTET STRING 

--ChannelInfo extension elements
EdcaParameterSet ::= SEQUENCE{
	acbeRecord	EdcaParameterRecord,
	acbkRecord	EdcaParameterRecord,
	acviRecord	EdcaParameterRecord,
	acvoRecord	EdcaParameterRecord
	}

EdcaParameterRecord ::= SEQUENCE {
	res	INTEGER (0..1),
	aci	INTEGER (0..3),
	acm 	INTEGER (0..1),
	aifsn	INTEGER (0..15),
	ecwMax	INTEGER (0..15),
	ecwMin	INTEGER (0..15),
	txopLimit	INTEGER (0..65535)
	}

ChannelAccess80211 ::= INTEGER {
	continuous	(0),
	alternatingSCH	(1),
	alternatingCCH	(2)
	} (0..255)


-- RoutingAdvertisement extension elements

SecondaryDns ::= IPv6Address

GatewayMacAddress ::= MACaddress



Latitude ::= SEQUENCE{
	fillBit	BIT STRING (SIZE(1)), -- set to '0' (MSB of Latitude)
	lat	INTEGER (-900000000..900000001)
	}

Longitude ::= INTEGER (-1800000000..1800000001)

Elevation ::= INTEGER (-4096..61439)


END

--<OSS.PDU>--
 
-- First edition 2016


ITSsa { iso (1) standard (0) localized(16460) sa(2) version0 (0)}  

DEFINITIONS AUTOMATIC TAGS ::= BEGIN

IMPORTS

IPv6Address, TXpower80211, ChannelNumber80211, EXT-TYPE, Extension, c-RepeatRate, c-2Dlocation, c-3Dlocation, c-advertiserID, RepeatRate, TwoDLocation, ThreeDLocation, AdvertiserIdentifier, c-ProviderServContext,c-IPv6Address, c-servicePort, c-ProviderMACaddress, c-RCPIthreshold, c-WSAcountThreshold, c-WSAcountThresInt, c-EDCAparameterSet, c-ChannelAccess, c-SecondaryDNS, c-GatewayMACaddress, c-LMchannelBusyRatio, c-LMrxCip, c-LMtxCip, c-LMpacketID, ProviderServiceContext, ServicePort, ProviderMacAddress, RcpiThreshold, WsaCountThreshold, WsaCountThresholdInterval, EdcaParameterSet, ChannelAccess80211, SecondaryDns, GatewayMacAddress, c-ExtendedChannelInfos, ExtendedChannelInfos, SAMapplicationData, c-SAMapplicationData FROM ITSee { iso (1) standard (0) localized(16460) ee(4) version0 (0)} 

PortNumber FROM ITSlm { iso (1) standard (0) localized (16460) lm(1) version0 (0)}  

ITSaid FROM CITSapplMgmtApplReg {iso(1) standard(0) cits-applMgmt (17419) applRegistry (2) version1 (1)} -- this is the p-encoded ITS-AID

;
-- End of IMPORTS

-- Service Advertisement Protocol messages

RsvAdvPrtVersion ::= INTEGER {
	c-rsvAdvPrtVersion2016	(3) -- current version number 
	}(0..15) -- Protocol version

-- Service Advertisement Message
Sam ::= SEQUENCE{
	version	RsvAdvPrtVersion,
	body	SamBody
	}

SamBody ::= SEQUENCE{
	changeCount	SrvAdvChangeCount,
	extensions	SrvAdvMsgHeaderExts OPTIONAL,
	serviceInfos	ServiceInfos OPTIONAL,
	channelInfos	ChannelInfos OPTIONAL,
	routingAdvertisement	RoutingAdvertisement OPTIONAL
	}

SrvAdvChangeCount ::= SEQUENCE{
	saID	SrvAdvID,
	contentCount	SrvAdvContentCount
	}

SrvAdvID ::= INTEGER(0..15)

SrvAdvContentCount ::= INTEGER(0..15)

-- SAM header extensions
SrvAdvMsgHeaderExts::= SEQUENCE OF SrvAdvMsgHeaderExt

SrvAdvMsgHeaderExt ::= Extension {{SrvAdvMsgHeaderExtTypes}}

SrvAdvMsgHeaderExtTypes EXT-TYPE ::= {
	{ RepeatRate 	IDENTIFIED BY c-RepeatRate } |
	{ TwoDLocation 	IDENTIFIED BY c-2Dlocation } |
	{ ThreeDLocation	IDENTIFIED BY c-3Dlocation } |
	{ AdvertiserIdentifier 	IDENTIFIED BY c-advertiserID } |
	{ ExtendedChannelInfos	IDENTIFIED BY c-ExtendedChannelInfos },
	...
	}

-- SAM Service Info Segment
ServiceInfos ::= SEQUENCE OF ServiceInfo -- '0' size allows to send only a routing advertisement

ServiceInfo ::= SEQUENCE {
	serviceID	ITSaid, -- ITS-AID
	channelIndex	ChannelIndex, -- 5 bits
	chOptions	ChannelOptions 
	}

ChannelOptions ::= SEQUENCE{
	systemService	SystemService OPTIONAL, 
	serviceProviderPort	ReplyAddress OPTIONAL,
	extensions	ServiceInfoExts OPTIONAL 
	}

ChannelIndex ::= INTEGER {
	notUsed	(0), -- no change of channel
	firstEntry	(1) 
	}(0..31)

ReplyAddress ::= PortNumber 

SystemService ::= SEQUENCE OF SystemServiceAndContext

SystemServiceAndContext ::= SamContext -- only ITS-AID = 0 allowed

-- Service Info Extensions
ServiceInfoExts ::= SEQUENCE OF ServiceInfoExt

ServiceInfoExt ::= Extension {{ServiceInfoExtTypes}}

ServiceInfoExtTypes EXT-TYPE ::= {
	{ ProviderServiceContext	IDENTIFIED BY c-ProviderServContext } |
	{ IPv6Address	IDENTIFIED BY c-IPv6Address } |
	{ ServicePort	IDENTIFIED BY c-servicePort } |
	{ ProviderMacAddress	IDENTIFIED BY c-ProviderMACaddress } |
	{ RcpiThreshold	IDENTIFIED BY c-RCPIthreshold } |
	{ WsaCountThreshold	IDENTIFIED BY c-WSAcountThreshold } |
	{ WsaCountThresholdInterval	IDENTIFIED BY c-WSAcountThresInt } |
	{ SAMapplicationData	IDENTIFIED BY c-SAMapplicationData },
	...
	}

-- Channel Info Segment
ChannelInfos ::= SEQUENCE OF ChannelInfo

ChannelInfo ::= SEQUENCE{
	operatingClass	OperatingClass80211,
	channelNumber	ChannelNumber80211,
	powerLevel	TXpower80211,
	dataRate	WsaChInfoDataRate,
	extensions	ChInfoOptions
	}

OperatingClass80211 ::= INTEGER (0..255)

WsaChInfoDataRate ::= SEQUENCE{
	adaptable	BIT STRING (SIZE(1)),
	dataRate	INTEGER (0..127)
	}

ChInfoOptions ::= SEQUENCE{
	option1	NULL OPTIONAL, -- not used
	option2	NULL OPTIONAL, -- not used
	option3	NULL OPTIONAL, -- not used
	option4	NULL OPTIONAL, -- not used
	option5	NULL OPTIONAL, -- not used
	option6	NULL OPTIONAL, -- not used
	option7	NULL OPTIONAL, -- not used
	extensions	ChannelInfoExts OPTIONAL
	} 

ChannelInfoExts ::= SEQUENCE OF ChannelInfoExt

ChannelInfoExt ::= Extension {{ChannelInfoExtTypes}}

ChannelInfoExtTypes EXT-TYPE ::= {
	{ EdcaParameterSet	IDENTIFIED BY c-EDCAparameterSet } |
	{ ChannelAccess80211	IDENTIFIED BY c-ChannelAccess },
	...
	}

-- Routing Advertisement
RoutingAdvertisement ::= SEQUENCE {
	lifetime	RouterLifetime,
	ipPrefix	IpV6Prefix,
	ipPrefixLength	IpV6PrefixLength,
	defaultGateway	IPv6Address,
	primaryDns	IPv6Address,
	extensions	RoutAdvertExts
	}

RouterLifetime ::= INTEGER (0..65535)

IpV6Prefix ::= OCTET STRING (SIZE (16))

IpV6PrefixLength ::= INTEGER (0..255)


-- Routing Advertisement extensions
RoutAdvertExts ::= SEQUENCE OF RoutAdvertExt

RoutAdvertExt ::= Extension {{RoutAdvertExtTypes}}

RoutAdvertExtTypes EXT-TYPE ::= {
	{ SecondaryDns	IDENTIFIED BY c-SecondaryDNS } |
	{ GatewayMacAddress	IDENTIFIED BY c-GatewayMACaddress },
	...
	}

-- Service Response Message
-- not supported in IEEE 1609.3™-2016
Srm ::= SEQUENCE{
	header	RsvAdvPrtVersion,
	body	SrmBody
	}

SrmBody ::= SEQUENCE{
	extensions	SRMextensions OPTIONAL,
	prvChannelsRq	SrmPrivateChannelsRq OPTIONAL,
	contexts	SrmContexts OPTIONAL,
	prvChannelsCf	SrmPrvChAllocConf OPTIONAL 
	}

SrmPrivateChannelsRq ::= SEQUENCE{
	portDynSam	PortNumber,
	allocReqs	SrmPrvChAllocReq
	}

SrmPrvChAllocReq ::= SEQUENCE OF ITSaid -- ITS-AIDs

SrmContexts ::= SEQUENCE OF SrmContext

SrmContext ::= SEQUENCE{
	context	SamContext,
	clientPort	PortNumber
	}

SrmPrvChAllocConf ::= SEQUENCE OF ITSaid -- ITS-AIDs

-- Service Advertisement Context info CLASS
-- A context is identified by the pair of ITS-AID and Context ID (&itsaidCtxRef)
-- ITS-AID has to identify an ITS application class (e.g. EFC)
-- Context ID is a context identifier unique for a given ITS application class

SA-CONTEXT ::= CLASS{
	&itsaidCtxRef	ItsAidCtxRef UNIQUE,
	&ContextInfo OPTIONAL
	}
	WITH SYNTAX {&ContextInfo IDENTIFIED BY &itsaidCtxRef}

SamContext ::= SEQUENCE{
	itsaidCtxRef	SA-CONTEXT.&itsaidCtxRef({AllsamContexts}),
	context	SA-CONTEXT.&ContextInfo({AllsamContexts}{@itsaidCtxRef})
	}

ItsAidCtxRef ::= SEQUENCE{
	itsaid	ITSaid,
	ctx	CtxRef
	}

CtxRef ::= INTEGER(0..255)
c-ctxRefNull CtxRef::=0 -- can be used with all values of ITS-AID
c-ctxRefMandApp CtxRef::=1 -- can be used with ITS-AID = 0

-- "Null-Context information"
c-CtxTypeSystemNull ItsAidCtxRef::={itsaid content:0, ctx c-ctxRefNull}
NullCtx ::= NULL -- don't care / don't know context

-- "Mandatory Application context information"
c-CtxTypeSystemMandApp ItsAidCtxRef::={itsaid content:0, ctx c-ctxRefMandApp}
MandAppCtx ::= SEQUENCE OF ItsAidCtxRef -- identifiers or mandatory applications

/* Examples
c-CtxType1 ItsAidCtxRef::={itsaid content:127, ctx 255}
c-CtxType2 ItsAidCtxRef::={itsaid extension:content:256, ctx 128}
c-CtxType3 ItsAidCtxRef::={itsaid extension:extension:content:16512, ctx 254}
*/

AllsamContexts SA-CONTEXT ::= {
	{ NullCtx	IDENTIFIED BY c-CtxTypeSystemNull} |
	{ MandAppCtx	IDENTIFIED BY c-CtxTypeSystemMandApp} ,
	...
	}

-- Sequence of 0 to n SRM extension elements
SRMextensions::=SEQUENCE OF SRMextension

-- A single SRM extension element
SRMextension::= Extension{{SRMexts}}

-- all available SRM Extensions

SRMexts EXT-TYPE::={
--	{ 	IDENTIFIED BY  } |
--	{ 	IDENTIFIED BY  } |
--	{ 	IDENTIFIED BY  },
	...
	}

END
